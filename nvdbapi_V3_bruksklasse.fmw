FME workspace nvdbapi_V3_bruksklasse.fmw

Parameters:
- apiFetchObjectURL = https://nvdbapiles-v3.atlas.vegvesen.no/vegobjekter/   # URL to NVDB api /vegobjekter end point (v3)
- objektTypeID = 904   # ID of object type from NVDB api

Creator
    GEOMTYPE = Geometry Object
    NUM = 1
    CREATED -> AttributeCreator
loop_fetchdata
    VEGOBJEKTURI = @Value(vegobjektURI)
    Tester_Failed -> DONE
    Tester_Passed -> AttributeCreator_2
DONE: Inspector [off]
Note: AttributeCreator_2 [AttributeCreator] / Attributes To Set: Attribute NameValueBruksklasseBruksklasse vinterMaks vogntoglengdeStrekningsbeskrivelseMaks totalvekt kjøretøy, skiltetMaks totalvekt vogntog, skiltetMerknad
AttributeCreator_2
    ATTR_LIST = Bruksklasse,,Bruksklasse vinter,,Maks vogntoglengde,,Strekningsbeskrivelse,,Maks totalvekt kjøretøy, skiltet,,Maks totalvekt vogntog, skiltet,,Merknad,
    -> XMLFeatureMapper_3
Note: This is where the magic happens! / xml=>FME features
XMLFeatureMapper_3
    ATTRIBUTE_XML = _url_contents
    CONFIGURATION_TYPE = Single xfMap file
    FEATURE_COUNT_PER_XML = _xml_feature_count_
    FEATURE_TYPE_ATTR = _xml_feature_type_
    MERGE_ATTRS = No
    NEW_ATTRIBUTES = nvdbId versjon startdato sluttdato sist_modifisert objektTypeId objektTypeNavn region{} kontraktsomrade{} riksvegrute{} wkt srid egengeometri strekningslengde vegsegmenter{}.segment{}
    SINGLE_XFMAP = $(FME_MF_DIR)xfmapDefintion_nvdbapi2fme_V3.xml
    XML_INPUT_TYPE = Attribute with XML document
    XML_SOURCE_NAME = _xml_source_
    MAPPED -> Tester_5
Note: Kun objekter med gyldig stedfesting / (F.eks. ingen historiske bruer)
Tester_5
    BOOL_OP = OR
    TEST_CLAUSE = TEST wkt NOT_ATTRIBUTE_IS_MISSING ""
    TEST_MODE = TEST
    PASSED -> AttributeCreator_6
    FAILED -> Ugyldig_stedfesting
Note: Explisit define the attributes! / Must be tuned to your object type definition! / (Just ignore the properties you don't need)
AttributeCreator_6
    ATTR_TABLE = SET_TO koordsys = epsg:@Value(srid)
    -> CoordinateSystemSetter
Note: Set coordinate system / EPSG:5973
CoordinateSystemSetter
    COORDSYS = @Value(koordsys)
    -> AttributeRemover
AttributeRemover
    LIST_ATTRS = _headers{} _headers{}.name _headers{}.value
    REMOVE_ATTRS = _creation_instance,_error,_http_status_code,_url_contents,_xml_feature_count_,_xml_feature_type_,_xml_source_,antall,returnert,start,strekningslengde,vegobjektURI,omradefilter,href,koordsys
    -> GeometryReplacer_3
    -> AttributeRemover_3
GeometryReplacer_3
    KIND_LONG = OGC Well Known Text
    REMOVE_ATTRIBUTE = Yes
    SOURCE = @Value(wkt)
    -> Hele_objekter
Hele_objekter: Inspector
vegsegmenter: Inspector
Ugyldig_stedfesting: Inspector [off]

Bookmark: Filter for område, egenskap etc
AttributeCreator
    ATTR_LIST = vegobjektURI,$(apiFetchObjectURL)$(objektTypeID)?inkluder=alle
    -> AttributeCreator_3
Note: Områdefilter / kommune=5029
AttributeCreator_3
    ATTR_LIST = omradefilter,kommune=5029
    -> AttributeCreator_4
Note: Føyer til filter
AttributeCreator_4
    ATTR_LIST = vegobjektURI,@Value(vegobjektURI)&@Value(omradefilter)
    -> loop_fetchdata [HTTPFetcher_Input]

Bookmark: Split object into individual road segments
AttributeRemover_3
    LIST_ATTRS = kontraktsomrade{} region{} riksvegrute{}
    REMOVE_ATTRS = objektTypeId,objektTypeNavn,sist_modifisert,srid,wkt
    -> ListExploder
ListExploder
    ATTR_ACCUM_MODE = Merge Incoming List
    ATTR_CONFLICT_RES = Use Incoming List
    INDEX_ATTR = _element_index
    LIST_ATTR = vegsegmenter{}
    LIST_FOUND -> ListExploder_2
    NOT_FOUND -> ListExploder_NotFound
ListExploder_2
    ATTR_ACCUM_MODE = Merge Incoming List
    ATTR_CONFLICT_RES = Use Incoming List
    INDEX_ATTR = _element_index
    LIST_ATTR = segment{}
    LIST_FOUND -> AttributeExposer
    NOT_FOUND -> ListExploder_NotFound
AttributeExposer
    ATTR_LIST = geometri{}.wkt{},vegsystemreferanse{}.kortform{0},veglenkesekvensid{},startposisjon{},sluttposisjon{},veglenketype{},typeVeg{},vegsystemreferanse{}.strekning{}.trafikantgruppe{}
    -> AttributeCreator_5
AttributeCreator_5
    ATTR_TABLE:
      SET_TO stedfesting = @Value(startposisjon{0})-@Value(sluttposisjon{0})\@@Value(veglenkesekvensid{0})
      SET_TO typeVeg = @Value(typeVeg{0})
      SET_TO vegsystemreferanse = @Value(vegsystemreferanse{0}.kortform{0})
      SET_TO trafikantgruppe = @Value(vegsystemreferanse{0}.strekning{0}.trafikantgruppe{0})
    -> GeometryReplacer_2
GeometryReplacer_2
    KIND_LONG = OGC Well Known Text
    REMOVE_ATTRIBUTE = Yes
    SOURCE = @Value(geometri{0}.wkt{0})
    -> AttributeRemover_2
AttributeRemover_2
    LIST_ATTRS = geometri{} geometri{}.wkt{} sluttposisjon{} startposisjon{} typeVeg{} veglenkesekvensid{} veglenketype{} vegsystemreferanse{} vegsystemreferanse{}.kortform{} vegsystemreferanse{}.strekning{} vegsystemreferanse{}.strekning{}.trafikantgruppe{}
    REMOVE_ATTRS = _element_index,egengeometri,segment
    -> vegsegmenter
ListExploder_NotFound: Inspector

FME custom transformer loop_fetchdata

Parameters:
- VEGOBJEKTURI = @Value(vegobjektURI)   # vegobjektURI

HTTPFetcher_Input (input)
    -> HTTPFetcher
HTTPFetcher__Rejected_: Inspector
Tester_Failed (output)
Note: New download URL / (next page in pagination)
AttributeCreator_4
    ATTR_LIST = vegobjektURI,@Value(href)
    -> HTTPFetcher_Input (output)
HTTPFetcher_Input (output)
Note: One batch (pagination) of data
Tester_Passed (output)

Bookmark: loop_fetchdata
Note: Download XML data from NVDB api
HTTPFetcher
    AUTH_METHOD = Basic
    ERROR_ATTR = _error
    FOLLOW_REDIRECTS = Yes
    PROXY_AUTH_METHOD = Basic
    REQUEST_HEADER:
      Accept: application/vnd.vegvesen.nvdb-v3-rev1+xml
      X-Client: FME http caller
      X-Kontaktperson: jan.kristian.jensen@vegvesen.no
    RESPONSE_HEADER_LIST_ATTR = _headers
    SAVE_FILE = No
    STATUS_CODE_ATTR = _http_status_code
    TARGET_ATTR = _url_contents
    TARGET_URL = @Value(vegobjektURI)
    USE_COOKIES = No
    VERIFY_SSL_CERTIFICATES = Yes
    -> XMLFeatureMapper_3
    <REJECTED> -> HTTPFetcher__Rejected_
    <REJECTED> -> Tester_Failed (output)
XMLFeatureMapper_3
    ATTRIBUTE_XML = _url_contents
    CONFIGURATION_TYPE = Embedded xfMap script
    FEATURE_COUNT_PER_XML = _xml_feature_count_
    FEATURE_TYPE_ATTR = _xml_feature_type_
    MERGE_ATTRS = Yes
    NEW_ATTRIBUTES = antall returnert start href
    SCRIPT_XFMAP:
      <?xml version="1.0"?>
      <xfMap>
       <feature-map multi-feature-construction="true">
          <mapping match="side/metadata">
             <feature-type> <literal expr="metadata"/> </feature-type>
          </mapping>
       </feature-map>
      <feature-content-map>

      	<mapping match="antall
      	   returnert
      	   neste/start
      	   neste/href
      	   ">
      		<attributes>
                 <attribute>
                    <name>   <matched expr="local-name"/> </name>
                    <value>  <extract expr="."/>  </value>
                 </attribute>
              </attributes>
           </mapping>

       </feature-content-map>
      </xfMap>
    XML_INPUT_TYPE = Attribute with XML document
    XML_SOURCE_NAME = _xml_source_
    MAPPED -> Tester
Tester
    BOOL_OP = OR
    TEST_CLAUSE = TEST @Value(returnert) > 0
    TEST_MODE = TEST
    PASSED -> Tester_Passed (output)
    PASSED -> AttributeCreator_4
    FAILED -> Tester_Failed (output)
